# SupervisoryLogic_System_Requirements

## System_Requirements: References to System_Requirements.docx (Container)
Read-only references to Microsoft Word document.

### 1 Overview: Overview (Informational)
1 Overview
This document describes high level requirements for the Supervisory Logic of the SEPIC Converter Embedded Software. The Software shall ensure maximum performance, safe operation, and protection of the power source such as the battery pack under diverse operating and environmental conditions.

### 2 System Interfaces: System Interfaces (Container)
2 System Interfaces

#### 2.1 Supervisory Logic Inputs: Supervisory Logic Inputs (Functional)
2.1 Supervisory Logic Inputs
| Bus Name | Data type | Units | Dims | From |
| --- | --- | --- | --- | --- |
| Max Load Current | single | A | 1 | Software Module “Load Current Limits” |
| SEPIC Voltage Desired | single | V | 1 | User Defined Values |
| LEDs Currents Desired | single | A | 6 | User Defined Values |
| Desired Operating Mode | enum | - | 1 | User Defined Values |
| SEPIC Voltage | single | V | 1 | Sensors |
| SEPIC Current | single | A | 1 | Sensors |
| PSU Voltage | single | V | 1 | Sensors |

#### 2.2 Supervisory Logic Outputs: Supervisory Logic Outputs (Functional)
2.2 Supervisory Logic Outputs
| Name | Data type | Units | To |
| --- | --- | --- | --- |
| SEPIC Voltage Reference | single | V | Voltage Controller |
| Zero Output | boolean | - | Voltage and LED Current Controller |
| Closed Loop Voltage Enable | boolean | - | Voltage Controller |
| Closed Loop LED Enable | boolean | - | CAN Bus (Motor Controller) |
| LED Currents Reference | single | A | LED Current Controller |
| Estimated Battery SoC | single | - | Diagnostic |

### 3 Supervisory Logic Software Components Requirements: Supervisory Logic Software Components Requirements (Container)
3 Supervisory Logic Software Components Requirements
Supervisory Logic software shall implement following list of software components:
1. Operating Mode And Error Logic
2. Battery SOC Estimation
3. Reference Output Safety Limitation

#### 3.1.2 Operating Mode Management High Level Requirements: Operating Mode Management High Level Requirements (Container)
3.1.2 Operating Mode Management High Level Requirements
OperatingModeManagement software component shall implement following functionalities:
· Divide operational states of system into 6 main operating states:
o All Controls Open Loop
o Voltage Control Open Loop, LEDs Closed Loop Control
o Voltage Control Closed Loop, LEDs Open Loop Control
o All Controls Loop Closed
o Automatic Operation
o No Output
· Has a parallel logic monitoring fault signal.
· Manage transitions between operation states based on operational state request from user, sensor measurement, faults, and battery pack measurements.

##### 3.1.2.1 Operating Mode Management Inputs: Operating Mode Management Inputs (Functional)
3.1.2.1 Operating Mode Management Inputs
| Name | Data type | Units | Dim | From |
| --- | --- | --- | --- | --- |
| Operating Mode | Enum | - | 1 | User Defined Values |
| Fault Flag Vector | Boolean | - | 10 | Battery SoC Estimation |
| Reset SoC Estimation Flag | Boolean | - | 1 | Battery SoC Estimation |
| SEPIC Voltage Desired | Single | V | 1 | User Defined Values |
| SEPIC Voltage Measured | Single | V | 1 | Sensors |

##### 3.1.2.2 Operating Mode Management Component Outputs: Operating Mode Management Component Outputs (Functional)
3.1.2.2 Operating Mode Management Component Outputs
| Name | Data type | Units | To |
| --- | --- | --- | --- |
| Enable Zero Output | Boolean | - | Voltage & Current Controller |
| Enable Closed Loop Voltage | Boolean | - | Voltage Controller |
| Enable Closed Loop LEDs | Boolean | - | LED Current Controller |

##### 3.1.2.3 All Controls Open Loop mode: All Controls Open Loop mode (Functional)
3.1.2.3 All Controls Open Loop mode
In this operating mode, the closed loop enable outputs for both voltage and LED current control are set to 0.

##### 3.1.2.4 Voltage Control Open Loop, LEDs: Voltage Control Open Loop, LEDs Closed Loop Control mode (Functional)
3.1.2.4 Voltage Control Open Loop, LEDs Closed Loop Control mode
In this operating mode, the closed loop enable output LED current control is to 1, whilst the voltage control is set to 0.

##### 3.1.2.5 Voltage Control Closed Loop, LED: Voltage Control Closed Loop, LEDs Open Loop Control mode (Functional)
3.1.2.5 Voltage Control Closed Loop, LEDs Open Loop Control mode
In this operating mode, the closed loop enable output LED current control is to 0, whilst the voltage control is set to 1.

##### 3.1.2.6 All Controls Loop Closed mode: All Controls Loop Closed mode (Functional)
3.1.2.6 All Controls Loop Closed mode
In this operating mode, the closed loop enable outputs for both voltage and LED current control are set to 1.

##### 3.1.2.7 Automatic Operation mode: Automatic Operation mode (Functional)
3.1.2.7 Automatic Operation mode
Automatic Operation mode will work in open loop as long as the error between voltage command and measured voltage is larger than 2 voltage, and will switch to closed loop voltage control once the error is under 1.5 voltage. The voltage control is closed first, then one sampling time (tick) after it will close the LED current control.

##### 3.1.2.8 No Output mode: No Output mode (Functional)
3.1.2.8 No Output mode
In this mode, the Zero Output Enable flag is set to true. This flag will be used by the controller to impose a 0% duty cycle

##### 3.1.2.9 Fault Flag Monitoring: Fault Flag Monitoring (Functional)
3.1.2.9 Fault Flag Monitoring
In this state machine, the Zero Output Enable is set to false if the Fault Exist Flag is false. The initial state should be true in order to ensure no power at the start of operation.
